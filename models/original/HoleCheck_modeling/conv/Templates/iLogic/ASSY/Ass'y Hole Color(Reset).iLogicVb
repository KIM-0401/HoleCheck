' <FireOthersImmediately>False</FireOthersImmediately>
Sub Main()
Dim oAssemblyDocument As AssemblyDocument = ThisDoc.Document
Dim oComponentOccurrences As ComponentOccurrences = oAssemblyDocument.ComponentDefinition.Occurrences

For Each oComponentOccurrence As ComponentOccurrence In oComponentOccurrences
	Me.SetSubHoleColor(oComponentOccurrence)
Next

End Sub

Sub SetSubHoleColor(ByRef oComponentOccurrence As ComponentOccurrence)
	If oComponentOccurrence.DefinitionDocumentType = DocumentTypeEnum.kAssemblyDocumentObject Then
		Dim oSubComponentOccurrences As ComponentOccurrences = oComponentOccurrence.Definition.Occurrences
		For Each oSubComponentOccurrence As ComponentOccurrence In oSubComponentOccurrences
			Me.SetSubHoleColor(oSubComponentOccurrence)
		Next

	ElseIf oComponentOccurrence.DefinitionDocumentType = DocumentTypeEnum.kPartDocumentObject Then
		Me.SetHoleColor(oComponentOccurrence)
	End If
End Sub

Sub SetHoleColor(ByRef oComponentOccurrence As ComponentOccurrence)
	Dim oPartComponentDefinition As PartComponentDefinition = oComponentOccurrence.Definition

	Dim sOccurrenceName As String = oComponentOccurrence.Name
	Dim oHolefeatures As HoleFeatures = oPartComponentDefinition.Features.HoleFeatures
	For Each oHolefeature As HoleFeature In oHolefeatures
		Feature.Color(sOccurrenceName, oHolefeature.Name) = "Default"
	Next
		Dim oFeatures As PartFeatures = oPartComponentDefinition.Features
	For Each RectPattern As RectangularPatternFeature In oFeatures.RectangularPatternFeatures
		RectPattern.Appearance = RectPattern.Definition.ParentFeatures(1).Appearance
	Next

	For Each CirPattern As CircularPatternFeature In oFeatures.CircularPatternFeatures
		CirPattern.Appearance = CirPattern.Definition.ParentFeatures(1).Appearance
	Next

	For Each MirrPattern As MirrorFeature In oFeatures.MirrorFeatures
		For i As Integer = 1 To MirrPattern.Faces.Count
			For Each oFeat As PartFeature In MirrPattern.Definition.ParentFeatures
				For j As Integer = 1 To oFeat.Faces.Count
					If oFeat.Faces(j).Evaluator.Area = MirrPattern.Faces(i).Evaluator.Area Then
						MirrPattern.Faces(i).Appearance = oFeat.Faces(j).Appearance
					End If
				Next j
			Next
		Next i
	Next

	For Each SketchPattern As SketchDrivenPatternFeature In oFeatures.SketchDrivenPatternFeatures
		SketchPattern.Appearance = SketchPattern.Definition.ParentFeatures(1).Appearance
	Next

End Sub
