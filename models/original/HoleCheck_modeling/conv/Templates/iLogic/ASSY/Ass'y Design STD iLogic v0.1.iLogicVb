' <FireOthersImmediately>False</FireOthersImmediately>
' <FireOthersImmediately>False</FireOthersImmediately>
'Hole Feature Coloring
Sub Main()
Dim oAssemblyDocument As AssemblyDocument = ThisDoc.Document
Dim oComponentOccurrences As ComponentOccurrences = oAssemblyDocument.ComponentDefinition.Occurrences

For Each oComponentOccurrence As ComponentOccurrence In oComponentOccurrences
	Me.SetSubHoleColor(oComponentOccurrence)
Next

End Sub

Sub SetSubHoleColor(ByRef oComponentOccurrence As ComponentOccurrence)
	If oComponentOccurrence.DefinitionDocumentType = DocumentTypeEnum.kAssemblyDocumentObject Then
		Dim oSubComponentOccurrences As ComponentOccurrences = oComponentOccurrence.Definition.Occurrences
		For Each oSubComponentOccurrence As ComponentOccurrence In oSubComponentOccurrences
			Me.SetSubHoleColor(oSubComponentOccurrence)
		Next

	ElseIf oComponentOccurrence.DefinitionDocumentType = DocumentTypeEnum.kPartDocumentObject Then
		Me.SetHoleColor(oComponentOccurrence)
	End If
End Sub

Sub SetHoleColor(ByRef oComponentOccurrence As ComponentOccurrence)
	Dim oPartComponentDefinition As PartComponentDefinition = oComponentOccurrence.Definition

	Dim sOccurrenceName As String = oComponentOccurrence.Name
	Dim oHolefeatures As HoleFeatures = oPartComponentDefinition.Features.HoleFeatures
	For Each oHolefeature As HoleFeature In oHolefeatures
		Dim sHoleName As String = oHolefeature.Name

		' Each Size Color Setting
		Dim M3 As String = "Cyan"
		Dim M4 As String = "Pink"
		Dim M5 As String = "Red"
		Dim M6 As String = "Yellow"
		Dim M8 As String = "Green"
		Dim M10 As String = "Violet"
		Dim M12 As String = "Orange"
		Dim M14 As String = "Magenta"
		Dim M16 As String = "Blue"
		Dim others As String = "Black"
		Dim PinHole As String = "White Oak"

		'Selected Hole
		'Tap Hole
		If oHolefeature.Tapped = True
			currentType = Feature.ThreadDesignation(sOccurrenceName, oHolefeature.Name)
			If currentType = "M3x0.5" Then
				Feature.Color(sOccurrenceName, oHolefeature.Name) = M3
			ElseIf currentType = "M4x0.7" Then
				Feature.Color(sOccurrenceName, oHolefeature.Name) = M4
			ElseIf currentType = "M5x0.8" Then
				Feature.Color(sOccurrenceName, oHolefeature.Name) = M5
			ElseIf currentType = "M6x1" Then
				Feature.Color(sOccurrenceName, oHolefeature.Name) = M6
			ElseIf currentType = "M8x1.25" Then
				Feature.Color(sOccurrenceName, oHolefeature.Name) = M8
			ElseIf currentType = "M10x1.5" Then
				Feature.Color(sOccurrenceName, oHolefeature.Name) = M10
			ElseIf currentType = "M12x1.75" Then
				Feature.Color(sOccurrenceName, oHolefeature.Name) = M12
			ElseIf currentType = "M14x2" Then
				Feature.Color(sOccurrenceName, oHolefeature.Name) = M14
			ElseIf currentType = "M16x2" Then
				Feature.Color(sOccurrenceName, oHolefeature.Name) = M16
			Else
				Feature.Color(sOccurrenceName, oHolefeature.Name) = others
			End If
		Else
			'Clearance Hole
			If oHolefeature.IsClearanceHole Then
				Dim HoleType As String = oHolefeature.ClearanceInfo.FastenerSize
				If HoleType = "M3" Then
					Feature.Color(sOccurrenceName, oHolefeature.Name) = M3
				ElseIf HoleType = "M4" Then
					Feature.Color(sOccurrenceName, oHolefeature.Name) = M4
				ElseIf HoleType = "M5" Then
					Feature.Color(sOccurrenceName, oHolefeature.Name) = M5
				ElseIf HoleType = "M6" Then
					Feature.Color(sOccurrenceName, oHolefeature.Name) = M6
				ElseIf HoleType = "M8" Then
					Feature.Color(sOccurrenceName, oHolefeature.Name) = M8
				ElseIf HoleType = "M10" Then
					Feature.Color(sOccurrenceName, oHolefeature.Name) = M10
				ElseIf HoleType = "M12" Then
					Feature.Color(sOccurrenceName, oHolefeature.Name) = M12
				ElseIf HoleType = "M16" Then
					Feature.Color(sOccurrenceName, oHolefeature.Name) = M16
				ElseIf HoleType = "Ø3" Then
					Feature.Color(sOccurrenceName, oHolefeature.Name) = PinHole
				ElseIf HoleType = "Ø4" Then
					Feature.Color(sOccurrenceName, oHolefeature.Name) = PinHole
				ElseIf HoleType = "Ø5" Then
					Feature.Color(sOccurrenceName, oHolefeature.Name) = PinHole
				ElseIf HoleType = "Ø6" Then
					Feature.Color(sOccurrenceName, oHolefeature.Name) = PinHole
				ElseIf HoleType = "Ø8" Then
					Feature.Color(sOccurrenceName, oHolefeature.Name) = PinHole
				ElseIf HoleType = "Ø10" Then
					Feature.Color(sOccurrenceName, oHolefeature.Name) = PinHole
				ElseIf HoleType = "Ø12" Then
					Feature.Color(sOccurrenceName, oHolefeature.Name) = PinHole
				ElseIf HoleType = "Ø14" Then
					Feature.Color(sOccurrenceName, oHolefeature.Name) = PinHole
				ElseIf HoleType = "Ø16" Then
					Feature.Color(sOccurrenceName, oHolefeature.Name) = PinHole
				ElseIf HoleType = "Ø18" Then
					Feature.Color(sOccurrenceName, oHolefeature.Name) = PinHole
				ElseIf HoleType = "Ø20" Then
					Feature.Color(sOccurrenceName, oHolefeature.Name) = PinHole
				ElseIf HoleType = "Ø22" Then
					Feature.Color(sOccurrenceName, oHolefeature.Name) = PinHole
				ElseIf HoleType = "Ø24" Then
					Feature.Color(sOccurrenceName, oHolefeature.Name) = PinHole
				ElseIf HoleType = "Ø30" Then
					Feature.Color(sOccurrenceName, oHolefeature.Name) = PinHole
				ElseIf HoleType = "Ø40" Then
					Feature.Color(sOccurrenceName, oHolefeature.Name) = PinHole
				ElseIf HoleType = "Ø50" Then
					Feature.Color(sOccurrenceName, oHolefeature.Name) = PinHole
				Else
					Feature.Color(sOccurrenceName, oHolefeature.Name) = others
				End If
			Else
				Feature.Color(sOccurrenceName, oHolefeature.Name) = others
			End If
		End If
	Next

	Dim oFeatures As PartFeatures = oPartComponentDefinition.Features
	For Each RectPattern As RectangularPatternFeature In oFeatures.RectangularPatternFeatures
		RectPattern.Appearance = RectPattern.Definition.ParentFeatures(1).Appearance
	Next

	For Each CirPattern As CircularPatternFeature In oFeatures.CircularPatternFeatures
		CirPattern.Appearance = CirPattern.Definition.ParentFeatures(1).Appearance
	Next

	For Each MirrPattern As MirrorFeature In oFeatures.MirrorFeatures
		For i As Integer = 1 To MirrPattern.Faces.Count
			For Each oFeat As PartFeature In MirrPattern.Definition.ParentFeatures
				For j As Integer = 1 To oFeat.Faces.Count
					If oFeat.Faces(j).Evaluator.Area = MirrPattern.Faces(i).Evaluator.Area Then
						MirrPattern.Faces(i).Appearance = oFeat.Faces(j).Appearance
					End If
				Next j
			Next
		Next i
	Next

	For Each SketchPattern As SketchDrivenPatternFeature In oFeatures.SketchDrivenPatternFeatures
		SketchPattern.Appearance = SketchPattern.Definition.ParentFeatures(1).Appearance
	Next

End Sub
