Dim i2 As Integer

If 수량_체결홀 = 2 Then
	
	
	If 길이방향_거리_체결홀 = (폭 - 홀간거리_체결홀*(수량_체결홀-1)) / 2  Then
	   MessageBox.Show("체결 홀 중앙 위치됨", "체결 홀 위치")
	
	ElseIf 길이방향_거리_체결홀 <> (폭 - 홀간거리_체결홀*(수량_체결홀-1)) / 2   Then
		i2 = MessageBox.Show("체결 홀을 중앙 기준 배치할까요?", "체결 홀 위치", MessageBoxButtons.YesNo) ' "yes6, no 7"
		
		If i2 = 6 Then
			길이방향_거리_체결홀 = (폭 - 홀간거리_체결홀*(수량_체결홀-1)) / 2 		
			iLogicVb.UpdateWhenDone = True			
				MessageBox.Show("체결 홀이 중앙에 배치됩니다.", "체결 홀 위치")

		ElseIf i2 = 7 Then
			길이방향_거리_체결홀 = 길이방향_거리_체결홀
				MessageBox.Show("센서홀 위치가 중앙이 아닐 수 있습니다.","체결 홀 위치")
		End If
		

	End If

 

ElseIf 수량_체결홀 > 2  Then

	
	If 길이방향_거리_체결홀 = (폭 - 홀간거리_체결홀*(수량_체결홀-1)) / 2  Then
	   MessageBox.Show("체결 홀 중앙 위치됨", "체결 홀 위치")
	
	ElseIf 길이방향_거리_체결홀 <> (폭 - 홀간거리_체결홀*(수량_체결홀-1)) / 2 	 Then
		i = MessageBox.Show("체결 홀을 중앙 기준 배치할까요?", "체결 홀 위치", MessageBoxButtons.YesNo) ' "yes6, no 7"
		
		If i = 6 Then
			길이방향_거리_체결홀 = (폭 - 홀간거리_체결홀*(수량_체결홀-1)) / 2 	
			iLogicVb.UpdateWhenDone = True			
				MessageBox.Show("체결 홀이 중앙에 배치됩니다.", "체결 홀 위치")

		ElseIf i = 7 Then
			길이방향_거리_체결홀 = 길이방향_거리_체결홀
				MessageBox.Show("센서홀 위치가 중앙이 아닐 수 있습니다.","체결 홀 위치")
		End If
		

	End If
	
ElseIf 수량_체결홀 < 2 Then
	MessageBox.Show("홀 수량 오류 입니다. 재지정 하세요.", "센서홀 위치")

End If
